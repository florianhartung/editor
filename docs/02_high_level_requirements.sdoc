[DOCUMENT]
TITLE: High-Level Requirements Specification
PREFIX: HLR-

[GRAMMAR]
ELEMENTS:
- TAG: SECTION
  PROPERTIES:
    IS_COMPOSITE: True
  FIELDS:
  - TITLE: UID
    TYPE: String
    REQUIRED: False
  - TITLE: LEVEL
    TYPE: String
    REQUIRED: False
  - TITLE: PREFIX
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: REQUIREMENT
  PROPERTIES:
    VIEW_STYLE: Table
  FIELDS:
  - TITLE: UID
    TYPE: String
    REQUIRED: False
  - TITLE: TITLE
    TYPE: String
    REQUIRED: False
  - TITLE: STATEMENT
    TYPE: String
    REQUIRED: False
  - TITLE: RATIONALE
    TYPE: String
    REQUIRED: False
  - TITLE: COMMENT
    TYPE: String
    REQUIRED: False
  RELATIONS:
  - TYPE: Parent
  - TYPE: File

[REQUIREMENT]
UID: HLR-1
TITLE: Positional Keymaps
STATEMENT: >>>
The editor shall support positional keymaps, i.e. keys mapped based solely on their position.
<<<
RATIONALE: >>>
Positional keymaps have their pros and cons.

**Pros**

- Bigrams can be optimized better

**Cons**

- More complex
- Harder to exchange common keybindings between users
<<<
COMMENT: >>>
https://ki-editor.org/docs/core-concepts/#2-positional-keymaps
<<<
COMMENT: >>>
TODO: Add positional coherence & travel distance optimization
<<<

[REQUIREMENT]
UID: HLR-2
TITLE: Orthogonality
RELATIONS:
- TYPE: Parent
  VALUE: SYS-11
- TYPE: Parent
  VALUE: SYS-16
- TYPE: Parent
  VALUE: SYS-20

[REQUIREMENT]
UID: HLR-3
TITLE: Correct Text Manipulation
STATEMENT: >>>
Text manipulation operations shall use the Unicode Standard for the definitions of graphemes and words.
<<<
RELATIONS:
- TYPE: Parent
  VALUE: SYS-1
- TYPE: Parent
  VALUE: SYS-16

[TEXT]
STATEMENT: >>>
- orthogonal bindings, as child of intuitive design
- transparent configuration format, child of intuitive
- in-editor keybinds cheatsheets, child of intuitive
- (derived requirement?) correctness: font rendering, unicode handling, etc.
<<<
